# Specification: Specification Document
- Description: Requirements Document

## R18 (Headline Type)
Introduction

## R15 (Requirement Type)
The purpose of this specification is to identify the behaviour of the lastChange attribute of Identifiable elements of ReqIF

## R16 (Requirement Type)
The lastChange Attribute is of the type dateTime with the following format: CCYY-MM-DDThh:mm:ss with optional time zone indicator as a suffix [+|-]hh:mm

Example: 2005-03-04T10:24:18+01:00 (MET time zone)

## R17 (Headline Type)
ReqIF Elements

## R11 (Requirement Type)
Identifiable
- Set After: - Creation

### R12 (Requirement Type)
AccessControlledElement

#### R5 (Requirement Type)
AttributeDefinition (AttributeDefinitionString, AttributeDefinitionBoolean, ...)

#### R9 (Requirement Type)
SpecHierarchy
- Set After: - The order of the SpecHierarchy has been changed

### R13 (Requirement Type)
SpecType

#### R6 (Requirement Type)
SpecificationType

#### R7 (Requirement Type)
SpecObjectType

#### R8 (Requirement Type)
SpecRelationType

### R14 (Requirement Type)
SpecElementWithAttributes
- Set After: - A corresponding AttributeValue has been changed

#### R2 (Requirement Type)
Specification

#### R3 (Requirement Type)
SpecRelation

#### R1 (Requirement Type)
SpecObject

### R10 (Requirement Type)
DatatypeDefinition (DatatypeDefinitionSimple, ...)

### R4 (Requirement Type)
EnumValue
