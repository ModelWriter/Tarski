# Specification: Specification Document
- Description: Software Specification

## rmf_14: Component: ReqIF Metamodel (Headline Type)

## rmf_1: Component: Serialization (Headline Type)

### rmf_16: Overview (Headline Type)

#### rmf_17: extend EMF Serialization Architecture (Spec Item Type)
The Serializer shall extend the already existing and powerful EMF serialization features. Esisting features shall still work as usual since RMF requires the full potential. Adaptation are needed for 
* reading multiple XML elements before an object can be created
* handling of references (references in RMF do not contain a resource)
- Behaviour in Eclipse Framework: The EMF serailization architecture is mature and covers most of the features required for serialization. Especially the handling of tool extension that might contain unknown XML is well supported.

### rmf_12: Tailoring EMF serialization (Headline Type)

#### rmf_13: XML element form default: qualified (Spec Item Type)
RMF shall serialize all XML elements that correspond to the ReqIF namespace in a qualified form. I.e.: all elements must be prefixed by its namespace prefix.
- Behaviour in Eclipse Framework: By default, EMF serializes XML elements (except the root element) in an unqualified form (no prefix is serialized in front of the XML element). This can be changed by adding the "namespace" information into the Extended Metadata Annotation in the meta model.
- Implementation Hint: Since we have full control over the ReqIF metamodel we can customize the behaviour by adding the "namespace" annotation in the metamodel

#### rmf_15: XML attribute form default: unqualified (Spec Item Type)
RMF shall serialize all XML attributes that relate to the ReqIF target namesoace in an unqualified form. (no prefix) The only exceptions are attributes that are related to a namespace that is different from the containing XML element. Example <REQ-IF xml:lang>
- Behaviour in Eclipse Framework: By default, EMF serializes XML attributes in an unqualified form. This can be changed by adding the "namespace" information into the Extended Metadata Annotation in the meta model
- Implementation Hint: Since we have full control over the ReqIF metamodel we can customize the behaviour by adding the "namespace" annotation in the metamodel

#### rmf_18: Rule for containment references with upper multiplicity 1 (Spec Item Type)
RMF shall serialized and deserialized containment references that use the following pattern: 
<UPPER-CASE-FEATURE-NAME>
   <UPPER-CASE-CLASS-NAME>
  …
  </UPPER-CASE-CLASS-NAME>
</UPPER-CASE-FEATURE-NAME>
- Behaviour in Eclipse Framework: By default, EMF serializes containmeent references using the following pattern:
  <featureName xsi:type="Class">
  …
  </featureName>

  By means of the "name" attribute of ExtendedMetadata EMF can use different names for Features and Classes in the XML representation:
  <UPPER-CASE-FEATURE-NAME xsi:type="UPPER-CASE-CLASS-NAME">
  …
  </UPPER-CASE-FEATURE-NAME >

  It is not possible to replace xsi:type= attribute by a nested element
- Implementation Hint: An additonal functionality is required in the XMLHandler and the XMLSaveImpl.

  The additional functionality is triggerd by an additonal RMF metadata annotation in the metamodel. This avoids dependencies to the ReqIF model and doesn' influence other EMF serialization features.

  The metadata of the feature contains:
  featureWrapperElement=false
  featureElement=true
  classWrapperElement=false
  classElement=true
  name=UPPER-CASE-FEATURE-NAME

  the metadata of the class contains:
  name=UPPER-CASE-CLASS-NAME

#### rmf_19: Rule for containment references with upper multiplicity >1 (Spec Item Type)
RMF shall serialized and deserialized containment references that use the following pattern: 
<UPPER-CASE-FEATURE-NAME>
   <UPPER-CASE-CLASS-NAME>
  …
  </UPPER-CASE-CLASS-NAME>
   <UPPER-CASE-CLASS-NAME>
  …
  </UPPER-CASE-CLASS-NAME>
</UPPER-CASE-FEATURE-NAME>
- Behaviour in Eclipse Framework: By default, EMF serializes containment references using the following pattern:
  <featureName xsi:type="Class">
  …
  </featureName>
  <featureName xsi:type="Class">
  …
  </featureName>

  By means of the "name" attribute of ExtendedMetadata EMF can use different names for Features and Classes in the XML representation:
  <UPPER-CASE-FEATURE-NAME xsi:type="UPPER-CASE-CLASS-NAME">
  …
  </UPPER-CASE-FEATURE-NAME >
  <UPPER-CASE-FEATURE-NAME xsi:type="UPPER-CASE-CLASS-NAME">
  …
  </UPPER-CASE-FEATURE-NAME >

  It is not possible to replace xsi:type= attribute by a nested element
  that is contained in a single wrapper element
- Implementation Hint: An additonal functionality is required in the XMLHandler and the XMLSaveImpl.

  The additional functionality is triggerd by an additonal RMF metadata annotation in the metamodel. This avoids dependencies to the ReqIF model and doesn' influence other EMF serialization features.

  The metadata of the feature contains:
  featureWrapperElement=true
  featureElement=false
  classWrapperElement=false
  classElement=true
  wrapperName=UPPER-CASE-FEATURE-NAME

  the metadata of the class contains:
  name=UPPER-CASE-CLASS-NAME

### rmf_20: Performance Optimization (Headline Type)

#### rmf_25: defer reference resolution (Spec Item Type)

#### rmf_26: use id to object map? (Spec Item Type)

#### rmf_27: use new EMF deserializiation methods (Spec Item Type)
- Implementation Hint: options.put(XMLResource.OPTION_USE_DEPRECATED_METHODS, Boolean.FALSE);

  this requires namespace aware parser:
  parserFeatures.put(Constants.SAX_FEATURE_PREFIX + Constants.NAMESPACES_FEATURE, true);
  parserFeatures.put(Constants.SAX_FEATURE_PREFIX + Constants.NAMESPACE_PREFIXES_FEATURE, false);
  options.put(XMLResource.OPTION_PARSER_FEATURES, parserFeatures);options.put(XMLResource.OPTION_PARSER_PROPERTIES, parserProperties);

#### rmf_30: create proxy objects only if needed (Spec Item Type)

#### rmf_21: reuse parser (Spec Item Type)

#### rmf_29: schema instance pool (Spec Item Type)

#### rmf_23: reuse metadata (Spec Item Type)

#### rmf_28: unresolved id pool (Spec Item Type)

#### rmf_32: cache files in binary resource (Spec Item Type)

#### rmf_33: parse XHTML and tool extensions on demand only (Spec Item Type)

#### rmf_34: do not generate any data on load (e.g no IDs) (Spec Item Type)

### rmf_9: XHTML (Headline Type)

#### R6

### rmf_10: ReqIF (Headline Type)

### rmf_8 (Spec Item Type)

### rmf_11: Tool Extensions (Headline Type)

## rmf_7: References (Headline Type)

### R2: Edapt - Framework for Ecore model adaptation and instance migration (Reference Type)
- URL: http://www.eclipse.org/edapt/

### R18: Definition and Generation of Data Exchange Formats in AUTOSAR (Reference Type)
- URL: http://www.broerkens.de/publications/pagel_broerkens_ECMDA2006.pdf
- Author: Brörkens, Pagel

## R12 (Reference Type)

## rmf_22 (Spec Item Type)

## rmf_24 (Spec Item Type)

## R25 (Reference Type)

## rmf_31: Multi-File optimizations (Headline Type)
